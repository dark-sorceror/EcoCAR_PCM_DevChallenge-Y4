# DevChallengeETRSReqs

## ETRS 1: The PSC shall command "TransmissionPosition" to replicate the highest priority range change request from the vehicle when the corresponding conditions are met (Functional)

### ETRS 1.1: If "ElectronicTransmissionRangeSel" indicates PARK or "ParktoChargeRequested" is True and "ElectricParkBrakeApplied" is True and "ElectricParkBrakeAvailable" is Available and "VehicleSpeed" is less than 0.5 , "TransmissionPosition" shall indicate PARK (Functional)

#### ETRS 1.1.1: When "ParktoChargeRequested" is True and "TransmissionPosition" is PARK, the PSC shall keep "TransmissionPosition" in PARK (Functional)

### ETRS 1.2: If "ElectronicTransmissionRangeSel" indicates REVERSE and "ElectricParkBrakeApplied" is False and the Propulsion system is Active, "TransmissionPosition" shall indicate REVERSE (Functional)
If "ElectronicTransmissionRangeSel" indicates REVERSE and "ElectricParkBrakeApplied" is False and the Propulsion system is Active, "TransmissionPosition" shall indicate REVERSE
// to make sure that etrs = rev has the intended effect and moves the transmission to rev
POSSIBLE TESTS / INPUT SIGNALS
1.) test ElectronicTransmissionRangeSel = REVERSE all the way, ElectricParkBrakeApplied == 2 all the way, VehicleSystemEnabled == 1 all the way
- success state
3.) test ElectronicTransmissionRangeSel = drive all the way, ElectricParkBrakeApplied == 2 all the way, VehicleSystemEnabled == 1 all the way
- expecting fail state (stuck in drive)
4.) test ElectronicTransmissionRangeSel = REVERSE all the way, ElectricParkBrakeApplied == 1 all the way, VehicleSystemEnabled == 1 all the way
- expecting fail state (stuck in park)
5.) test ElectronicTransmissionRangeSel = drive 0<t<10, ElectronicTransmissionRangeSel = REVERSE 10<t<35, ElectricParkBrakeApplied == 1 all the way, VehicleSystemEnabled == 1 all the way
- temporal test, expecting success state for t>10
OTHER INPUT VARIABLES
ElectricParkBrakeAvailable
ElectricParkBrakeAvailable == 1
doesn't matter really in this case, but prolly want that in general ;D
ParktoChargeRequested
ParktoChargeRequested == 0
We want to go to reverse, not go to park
Park_BrakePressed
Park_BrakePressed == 1
to get out of park
VehicleSpeed
VehicleSpeed < 0.5
VehicleSpeed == 0.1
to get out of park
HVShutdownRequested - High Voltage Shutdown, condition to force it to go into neutral
HVShutdownRequested == 0
We dont want to shut down power, we need power to go in REVERSE

### ETRS 1.3: If "ElectronicTransmissionRangeSel" indicates NEUTRAL, "TransmissionPosition" shall indicate NEUTRAL (Functional)
If "ElectronicTransmissionRangeSel" indicates NEUTRAL, "TransmissionPosition" shall indicate NEUTRAL
// to make sure that etrs = neutral has the intended effect and moves the transmission to neutral
POSSIBLE TESTS / INPUT SIGNALS
1.) test ElectronicTransmissionRangeSel = NEUTRAL all the way
- success state
2.) test ElectronicTransmissionRangeSel = drive all the way
- expecting fail state (stuck in drive)
3.) test ElectronicTransmissionRangeSel = rev all the way
- expecting fail state (stuck in rev)
4.) test ElectronicTransmissionRangeSel = rev 0<t<10, ElectronicTransmissionRangeSel = NEUTRAL 10<t<35
- temporal test, expecting success state for t>10
OTHER INPUT VARIABLES
ElectricParkBrakeApplied
ElectricParkBrakeApplied == 0
ElectricParkBrakeAvailable
ElectricParkBrakeAvailable == 1
doesn't matter really in this case, but prolly want that in general ;D
ParktoChargeRequested
ParktoChargeRequested == 0
We want to stay in neutral, not go to park
Park_BrakePressed
Park_BrakePressed == 1
VehicleSpeed
VehicleSpeed < 0.5
VehicleSpeed == 0.1
HVShutdownRequested - High Voltage Shutdown, condition to force it to go into neutral
HVShutdownRequested == 0
We want ElectronicTransmissionRangeSel to control the car going into neutral, not these other variables.
VehicleSystemEnabled - is the propulsion system on, can’t go into reverse or drive w/o this, basically shutting off the engine
VehicleSystemEnabled == 1
Doesn't rlly matter in this case

### ETRS 1.4: If "ElectronicTransmissionRangeSel" indicates DRIVE and "ElectricParkBrakeApplied" is False AND the Propulsion system is Active, "TransmissionPosition" shall indicate DRIVE (Functional)
If "ElectronicTransmissionRangeSel" indicates DRIVE and "ElectricParkBrakeApplied" is False AND the Propulsion system is Active, "TransmissionPosition" shall indicate DRIVE
//just testing if it can go into drive
POSSIBLE TESTS / INPUT SIGNALS
1.) test ElectronicTransmissionRangeSel = drive all the way && ElectricParkBrakeApplied = false all the way && VehicleSystemEnabled == 1 all the way
- success state
2.) test ElectronicTransmissionRangeSel = drive all the way && ElectricParkBrakeApplied = false all the way && VehicleSystemEnabled == 0 all the way
- expecting fail state (stuck in neutral)
3.) test ElectronicTransmissionRangeSel = drive all the way && ElectricParkBrakeApplied = True all the way && VehicleSystemEnabled == 1 all the way
- expecting fail state (stuck in neutral)
4.) test ElectronicTransmissionRangeSel = rev all the way && ElectricParkBrakeApplied = false all the way && VehicleSystemEnabled == 1 all the way
- expecting fail state (stuck in rev)
5.) test ElectronicTransmissionRangeSel = drive all the way && ElectricParkBrakeApplied = True 0<t<10, ElectricParkBrakeApplied = False 10<t<35. && VehicleSystemEnabled == 1 all the way
- temporal test, expecting succes state for t>10
6.) test ElectronicTransmissionRangeSel = rev 0<t<10, ElectronicTransmissionRangeSel = drive 10<t<35 && ElectricParkBrakeApplied all the way.&& VehicleSystemEnabled == 1 all the way
- temporal test, expecitng succes state for t>10
OTHER INPUT VARIABLES
ElectricParkBrakeAvailable
ElectricParkBrakeAvailable == 1
doesn't matter really in this case, but prolly want that in general ;D
ParktoChargeRequested
ParktoChargeRequested == 0
Since we are going to drive we don't want this at all.
Park_BrakePressed
Park_BrakePressed == 1
Just in case another transition on the way to drive needs it to be activated
VehicleSpeed
VehicleSpeed < 0.5
VehicleSpeed == 0.1
Just in case another transition on the way to drive needs it to be < 0.5
HVShutdownRequested - High Voltage Shutdown, condition to force it to go into neutral or park
HVShutdownRequested == 0
Since we are going to drive we don't want this at all.

## ETRS 2: The PSC shall indicate NEUTRAL via "TransmissionPosition" when the parking brake is not in the correct status for the requested gear (Functional)

### ETRS 2.1: If "ElectronicTransmissionRangeSel" indicates DRIVE/REVERSE and the ElectricParkBrakeApplied is False, the PSC shall indicate NEUTRAL via "TransmissionPosition" (Functional)
If "ElectronicTransmissionRangeSel" indicates DRIVE/REVERSE (2 or 4) and the ElectricParkBrakeApplied is True(1), the PSC shall indicate NEUTRAL via "TransmissionPosition"
ADVANCED CASES
1.) NOBRAKE_rev
ElectronicTransmissionRangeSel == 2
ElectricParkBrakeApplied == 2
If in PARK
park>neut: TransmissionPosition == 1 or 5
If in NEUTRAL
neut>park: TransmissionPosition == 5
neut>rev: TransmissionPosition == 3
neut>drive: TransmissionPosition == 5
If in DRIVE
drive>neut: TransmissionPosition == 5
If in REVERSE
rev>neut: TransmissionPosition == 3
Finally: TransmissionPosition == 1 | TransmissionPosition == 3 | TransmissionPosition == 5
2.) NOBRAKE_drive
ElectronicTransmissionRangeSel == 2
ElectricParkBrakeApplied == 2
If in PARK
park>neut: TransmissionPosition == 1 or 5
If in NEUTRAL
neut>park: TransmissionPosition == 5
neut>rev: TransmissionPosition == 5
neut>drive: TransmissionPosition == 7
If in DRIVE
drive>neut: TransmissionPosition == 7
If in REVERSE
rev>neut: TransmissionPosition == 5
Finally: TransmissionPosition == 1 | TransmissionPosition == 5 | TransmissionPosition == 7
POSSIBLE TESTS / INPUT SIGNALS
1.) test etrs = drive all the way && parkbrakeApplied = false all the way
- success state
2.) test etrs = reverse all the way && parkbrakeApplied = false all the way
- succes state
3.) test etrs = drive all the way && parkbrakeApplied = True all the way
- expecting fail state (stuck in drive)
4.) test etrs = rev all the way && parkbrakeApplied = True all the way
- expecting fail state (stuck in rev)
5.) test etrs = drive all the way && parkbrakeApplied = Unknown all the way
- expecting fail state (stuck in drive)
6.) test etrs = drive all the way && parkbrakeApplied = True 0<t<10, parkbrakeApplied = False 10<t<35.
- temporal test, expecting succes state for t>10
7.) test etrs = park 0<t<10, etrs = rev 10<t<35 && parkbrakeApplied all the way.
- temporal test, expecitng succes state for t>10
OTHER INPUT VARIABLES
ElectricParkBrakeAvailable
ElectricParkBrakeAvailable == 1
doesn't matter really in this case, but prolly want that in general ;D
ParktoChargeRequested
ParktoChargeRequested == 1
All the way, what gets us from drive/rev towards neutral
Park_BrakePressed
Park_BrakePressed == 1
VehicleSpeed
VehicleSpeed < 0.5
VehicleSpeed == 0.1
HVShutdownRequested - High Voltage Shutdown, condition to force it to go into neutral or park
HVShutdownRequested == 0
Doesn’t rlly matter in this case
VehicleSystemEnabled - is the propulsion system on, can’t go into reverse or drive w/o this, basically shutting off the engine
Not sure if you can do this since there is no yellow box indicating inputs on the flowchart, but it will go to reverse or drive immediately unless this is == 0.

### ETRS 2.2: If "ElectronicTransmissionRangeSel" indicates PARK or "ParktoChargeRequested" is True and the "ElectricParkBrakeApplied" is False, the PSC shall indicate NEUTRAL via "TransmissionPosition" (Functional)
If "ElectronicTransmissionRangeSel" indicates PARK(1) or "ParktoChargeRequested" is True(1) and the "ElectricParkBrakeApplied" is False(2), the PSC shall indicate NEUTRAL via "TransmissionPosition"
// we are checking that the car doesnt go into park if/until the park brake is applied
ADVANCED CASES
1.) YESBRAKE
ElectronicTransmissionRangeSel == 1
ParktoChargeRequested == 1
ElectricParkBrakeApplied == 1
If in PARK
park>neut: TransmissionPosition == 1
If in NEUTRAL
neut>park: TransmissionPosition == 1 or 5
neut>rev: TransmissionPosition == 5
neut>drive: TransmissionPosition == 5
If in DRIVE
drive>neut: TransmissionPosition == 5
If in REVERSE
rev>neut: TransmissionPosition == 5
Finally: TransmissionPosition == 1 | TransmissionPosition == 5
2.) NOTPARK
ElectronicTransmissionRangeSel == 2
ParktoChargeRequested == 1
ElectricParkBrakeApplied == 2
If in PARK
park>neut: TransmissionPosition == 1
If in NEUTRAL
neut>park: TransmissionPosition == 5
neut>rev: TransmissionPosition == 3
neut>drive: TransmissionPosition == 5
If in DRIVE
drive>neut: TransmissionPosition == 5
If in REVERSE
rev>neut: TransmissionPosition == 5
Finally: TransmissionPosition == 1 | TransmissionPosition == 5 | TransmissionPosition == 3
2.) NO_CHARGE_REQ
ElectronicTransmissionRangeSel == 1
ParktoChargeRequested == 0
ElectricParkBrakeApplied == 2
If in PARK
park>neut: TransmissionPosition == 1 or 5
If in NEUTRAL
neut>park: TransmissionPosition == 5
neut>rev: TransmissionPosition == 5
neut>drive: TransmissionPosition == 5
If in DRIVE
drive>neut: TransmissionPosition == 5
If in REVERSE
rev>neut: TransmissionPosition == 5
Finally: TransmissionPosition == 1 | TransmissionPosition == 5
//initially set above variables and a few others to a different value, to get it into neutral, cant test going into park if you are in park itself. Setting variable to above values leaves you stuck in park.
POSSIBLE TESTS / INPUT SIGNALS
1.) test ElectronicTransmissionRangeSel = park all the way && ParktoChargeRequested == True all the way && ElectricParkBrakeApplied = false all the way
- expecting pass, stay in neutral
2.) test ElectronicTransmissionRangeSel = park all the way && ParktoChargeRequested == True all the way && ElectricParkBrakeApplied = True all the way
- expecting fail, go into park
3.) test ElectronicTransmissionRangeSel = park all the way && ParktoChargeRequested == True all the way && ElectricParkBrakeApplied = false 0<t<10, ElectricParkBrakeApplied = True 10<t<35.
- temporal test, fail for t>10, shift into park
4.) test ElectronicTransmissionRangeSel = drive for 0<t<10, ElectronicTransmissionRangeSel = park 10<t<35 && ParktoChargeRequested == True all the way && ElectricParkBrakeApplied = True all the way.
- temporal test, fail for t>10, shift into park
OTHER INPUT VARAIBLES
ElectricParkBrakeAvailable
ElectricParkBrakeAvailable == 1
Park_BrakePressed
Park_BrakePressed == 1
Doesnt rlly matter
VehicleSpeed
VehicleSpeed < 0.5
VehicleSpeed == 0.1
HVShutdownRequested - High Voltage Shutdown, condition to force it to go into neutral or park
HVShutdownRequested == 0
Doesn’t rlly matter in this case
VehicleSystemEnabled - is the propulsion system on, can’t go into reverse or drive w/o this, basically shutting off the engine
VehicleSystemEnabled == 1

## ETRS 3: The PSC shall not allow unsafe gear changes while the vehicle is in motion (Functional)
| The PSC shall not allow unsafe gear changes while the vehicle is in motion |
| --- |

### ETRS 3.1: The PSC shall only allow a shift to PARK if the vehicle speed is below 0.5 km/h (Functional)

### ETRS 3.2: When the vehicle is in motion above 0.5 km/h, the PSC shall not allow a shift to the propulsion mode which does not correspond to the vehicle's direction (i.e., it would not allow shifting to reverse while the vehicle is moving forward) (Functional)

## ETRS 4: The PSC shall require the brake to be pressed for gear changes that could otherwise cause harm or significantly damage the vehicle (Functional)

### ETRS 4.1: The PSC shall not allow a shift out of PARK if the brake is not pressed (Functional)
